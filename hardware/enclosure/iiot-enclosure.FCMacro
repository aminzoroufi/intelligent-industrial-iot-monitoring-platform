# FreeCAD 1.x parametric rebuild script; generated from hardware/design.json
import FreeCAD as App
import Part

doc = App.newDocument("IIoT_Enclosure")
width = 108.0
depth = 78.0
wall = 2.4
floor = 3.0
height = 28.0
outer = Part.makeBox(width, depth, height + floor)
inner = Part.makeBox(width - 2 * wall, depth - 2 * wall, height + 1, App.Vector(wall, wall, floor))
base_shape = outer.cut(inner)
base = doc.addObject("PartDesign::Feature", "Base")
base.Label = "Parametric enclosure base"
base.Shape = base_shape
lid = doc.addObject("PartDesign::Feature", "Lid")
lid.Label = "Exploded lid"
lid.Shape = Part.makeBox(width, depth, 2.4, App.Vector(0, 0, height + 12))
doc.recompute()
doc.saveAs(App.getUserAppDataDir() + "iiot-enclosure.FCStd")
Part.export([base, lid], App.getUserAppDataDir() + "iiot-enclosure-assembly.step")
